[DOCUMENT]
TITLE: Thread Scheduling
PREFIX: ZEP-SRS-2-

[GRAMMAR]
IMPORT_FROM_FILE: software_requirements.sgra

[TEXT]
STATEMENT: >>>
SPDX-License-Identifier: Apache-2.0
<<<

[[SECTION]]
TITLE: Multi-Core Thread Scheduling

[REQUIREMENT]
UID: ZEP-SRS-2-1
STATUS: Draft
TYPE: Functional
COMPONENT: Multi Core
TITLE: Support operation on more than one CPU
STATEMENT: >>>
The Zephyr RTOS shall support operation on more than one physical CPU sharing the same kernel state.
<<<
RELATIONS:
- TYPE: Parent
  VALUE: ZEP-SYRS-11

[REQUIREMENT]
UID: ZEP-SRS-2-2
STATUS: Draft
TYPE: Functional
COMPONENT: Multi Core
TITLE: Running threads on specific CPUs
STATEMENT: >>>
The Zephyr RTOS shall provide an interface for running threads on specific sets of CPUs ( default is 1 CPU).
<<<
USER_STORY: >>>
As a Zephyr RTOS user I want Zephyr OS to be able to specify the CPU core or the set of CPU cores on which a thread shall be executed.
<<<
RELATIONS:
- TYPE: Parent
  VALUE: ZEP-SYRS-12

[REQUIREMENT]
UID: ZEP-SRS-2-3
STATUS: Draft
TYPE: Functional
COMPONENT: Multi Core
TITLE: Exclusion between physical CPUs
STATEMENT: >>>
The Zephyr RTOS shall provide an interface for mutual exclusion between multiple physical CPUs.
<<<
USER_STORY: >>>
As a Zephyr RTOS user I want Zephyr OS to provide synchronization mechanisms between the CPU cores and the access to common resources.
<<<
RELATIONS:
- TYPE: Parent
  VALUE: ZEP-SYRS-11

[[/SECTION]]

[[SECTION]]
TITLE: Thread Scheduling

[REQUIREMENT]
UID: ZEP-SRS-2-4
STATUS: Draft
TYPE: Functional
COMPONENT: Thread Scheduling
TITLE: Scheduling a thread based on an event
STATEMENT: >>>
The Zephyr RTOS shall provide an interface to schedule a thread based on an event.
<<<
USER_STORY: >>>
As a Zephyr RTOS user, I want to be able to execute work which reacts on events and interrupts the current executed work.
<<<
RELATIONS:
- TYPE: Parent
  VALUE: ZEP-SYRS-15

[REQUIREMENT]
UID: ZEP-SRS-2-5
STATUS: Draft
TYPE: Functional
COMPONENT: Thread Scheduling
TITLE: Deadline Scheduling Priorities
STATEMENT: >>>
The Zephyr RTOS shall organize running threads by earliest deadline first priority.
<<<
USER_STORY: >>>
As a Zephyr RTOS user, I want to be able to schedule threads by earliest deadline first.
<<<
RELATIONS:
- TYPE: Parent
  VALUE: ZEP-SYRS-17

[REQUIREMENT]
UID: ZEP-SRS-2-6
STATUS: Draft
TYPE: Functional
COMPONENT: Thread Scheduling
TITLE: Work Queue utility capable of running preemptible work items
STATEMENT: >>>
The Zephyr RTOS shall provide a thread-pooled work queue utility capable of running preemptible work items with specific scheduler priorities.
<<<
USER_STORY: >>>
As a Zephyr RTOS user, I want to be able to add work items in a thread work queue with different priorities and these shall be scheduled according their priorities.
<<<
RELATIONS:
- TYPE: Parent
  VALUE: ZEP-SYRS-33

[REQUIREMENT]
UID: ZEP-SRS-2-7
STATUS: Draft
TYPE: Functional
COMPONENT: Thread Scheduling
TITLE: Run user supplied functions in-order in a separate thread(s)
STATEMENT: >>>
The Zephyr RTOS shall provide an interface for running user-supplied functions.
<<<
USER_STORY: >>>
As a Zephyr RTOS user, I want to be able to run functions in-order in a separated thread/threads.
<<<
RELATIONS:
- TYPE: Parent
  VALUE: ZEP-SYRS-15

[REQUIREMENT]
UID: ZEP-SRS-2-8
STATUS: Draft
TYPE: Functional
COMPONENT: Thread Scheduling
TITLE: Organize running threads into a fixed list
STATEMENT: >>>
The Zephyr RTOS shall organize running threads into a fixed list of numeric priorities.
<<<
USER_STORY: >>>
As a Zephyr RTOS user, I want that the OS organize running threads in a fixed list of numeric priorities.
<<<
RELATIONS:
- TYPE: Parent
  VALUE: ZEP-SYRS-17

[REQUIREMENT]
UID: ZEP-SRS-2-9
STATUS: Draft
TYPE: Functional
COMPONENT: Thread Scheduling
TITLE: Preemption support
STATEMENT: >>>
The Zephyr RTOS shall support preemption of a running thread by a higher priority thread.
<<<
USER_STORY: >>>
As a Zephyr RTOS user, I want that the OS preempt running threads by a thread with higher priority.
<<<
RELATIONS:
- TYPE: Parent
  VALUE: ZEP-SYRS-16
- TYPE: Parent
  VALUE: ZEP-SYRS-17

[REQUIREMENT]
UID: ZEP-SRS-2-10
STATUS: Draft
TYPE: Functional
COMPONENT: Thread Scheduling
TITLE: Un-preemptible thread priorities
STATEMENT: >>>
The Zephyr RTOS shall support thread priorities which cannot be preempted by other user threads.
<<<
USER_STORY: >>>
As a Zephyr RTOS user, I want to be able to configure thread prioritizes which cannot be preempted by other user threads.
<<<
RELATIONS:
- TYPE: Parent
  VALUE: ZEP-SYRS-17

[REQUIREMENT]
UID: ZEP-SRS-2-11
STATUS: Draft
TYPE: Functional
COMPONENT: Thread Scheduling
TITLE: Time sharing of CPU resources
STATEMENT: >>>
The Zephyr RTOS shall support time sharing of CPU resources among threads of the same priority.
<<<
USER_STORY: >>>
As a Zephyr RTOS user, I want to be able to configure my RTOS in the way, that the CPU resources are shared evenly among executed threads of the same priority.
<<<
RELATIONS:
- TYPE: Parent
  VALUE: ZEP-SYRS-16
- TYPE: Parent
  VALUE: ZEP-SYRS-17

[REQUIREMENT]
UID: ZEP-SRS-2-12
STATUS: Draft
TYPE: Functional
COMPONENT: Thread Scheduling
TITLE: Scheduler lock
STATEMENT: >>>
The Zephyr RTOS shall provide an interface to temporarily prevent the scheduler from
preempting the current thread, creating a cooperative scheduling window, and to
subsequently unlock the scheduler and re-enable preemption.
<<<
USER_STORY: >>>
As a Zephyr RTOS user, I want to lock the scheduler to protect a short critical section
from preemption without the overhead of disabling interrupts.
<<<
RELATIONS:
- TYPE: Parent
  VALUE: ZEP-SYRS-16
- TYPE: Parent
  VALUE: ZEP-SYRS-17

[[/SECTION]]
