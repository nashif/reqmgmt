[DOCUMENT]
TITLE: Freedom from Interference
PREFIX: ZEP-SRS-42-

[GRAMMAR]
IMPORT_FROM_FILE: software_requirements.sgra

[TEXT]
STATEMENT: >>>
SPDX-License-Identifier: Apache-2.0
<<<

[TEXT]
STATEMENT: >>>
Freedom from Interference (FFI) is the property that a fault or misbehaviour in one
software component cannot compromise the correct execution of another. Requirements in
this document cover four aspects: spatial isolation (memory), stack integrity, temporal
isolation (CPU time), and fault containment.

STATUS convention: Active means the requirement is satisfied by the current Zephyr
implementation. Draft means the requirement identifies a gap not yet addressed in
Zephyr and is recorded here so that future work can be tracked against it.
<<<

[TEXT]
STATEMENT: >>>
Spatial Isolation
<<<

[REQUIREMENT]
UID: ZEP-SRS-42-1
STATUS: Active
TYPE: Functional
COMPONENT: Freedom From Interference
TITLE: Memory domain partitioning for user thread groups
STATEMENT: >>>
The Zephyr RTOS shall support the grouping of user threads into memory domains,
where each domain is defined by a set of non-overlapping memory partitions, and
a thread may only access memory that belongs to a partition in its assigned domain
in addition to its own stack buffer, program text, and read-only data.
<<<
USER_STORY: >>>
As a Zephyr RTOS user I want logically separate application components to be
confined to distinct memory regions so that a pointer error in one component
cannot read or corrupt the data of another component.
<<<
RELATIONS:
- TYPE: Parent
  VALUE: ZEP-SYRS-35

[REQUIREMENT]
UID: ZEP-SRS-42-2
STATUS: Active
TYPE: Functional
COMPONENT: Freedom From Interference
TITLE: Non-overlapping memory partitions within a domain
STATEMENT: >>>
The Zephyr RTOS shall reject at runtime any attempt to add a memory partition to a
domain that would overlap an existing partition within that domain.
<<<
USER_STORY: >>>
As a Zephyr RTOS user I want the kernel to enforce at configuration time that
partitions do not share addresses so that the isolation boundaries are always
well-defined.
<<<
RELATIONS:
- TYPE: Parent
  VALUE: ZEP-SYRS-35

[REQUIREMENT]
UID: ZEP-SRS-42-3
STATUS: Active
TYPE: Non-Functional
COMPONENT: Freedom From Interference
TITLE: Write-XOR-Execute enforcement for memory partitions
STATEMENT: >>>
When CONFIG_EXECUTE_XOR_WRITE is enabled, the Zephyr RTOS shall enforce that no
memory partition is simultaneously writable and executable, preventing code injection
via writable memory regions.
<<<
USER_STORY: >>>
As a Zephyr RTOS user on a safety-critical or security-sensitive system I want the
MPU/MMU hardware to prevent runtime code injection so that an attacker or a
corrupted data buffer cannot cause arbitrary code execution.
<<<
RELATIONS:
- TYPE: Parent
  VALUE: ZEP-SYRS-35

[REQUIREMENT]
UID: ZEP-SRS-42-4
STATUS: Draft
TYPE: Non-Functional
COMPONENT: Freedom From Interference
TITLE: Spatial isolation between supervisor-mode threads
STATEMENT: >>>
The Zephyr RTOS shall provide a mechanism to enforce memory access boundaries
between concurrently executing supervisor-mode (kernel) threads so that an erroneous
memory access in one supervisor thread cannot corrupt the data or stack of another
supervisor thread.

NOTE: This requirement is not currently met by the Zephyr implementation. When
CONFIG_USERSPACE is not enabled, all threads execute in privileged mode and share
the full address space without any MPU-enforced inter-thread boundary. This is a
known architectural gap for deployments that cannot enable userspace but still
require intra-kernel isolation.
<<<
USER_STORY: >>>
As a Zephyr RTOS user building a safety-critical system without a full userspace
partition, I want supervisor threads running different mixed-criticality application
components to be spatially isolated from each other so that a stray pointer in a
lower-criticality thread cannot corrupt a higher-criticality thread's data.
<<<
RELATIONS:
- TYPE: Parent
  VALUE: ZEP-SYRS-35

[TEXT]
STATEMENT: >>>
Stack Integrity
<<<

[REQUIREMENT]
UID: ZEP-SRS-42-5
STATUS: Active
TYPE: Functional
COMPONENT: Freedom From Interference
TITLE: Hardware-backed stack overflow detection
STATEMENT: >>>
When CONFIG_HW_STACK_PROTECTION is enabled, the Zephyr RTOS shall use
architecture-provided hardware (MPU guard region or equivalent) to detect stack
overflow for threads running in privileged mode and invoke the fatal error handler
upon detection.
<<<
USER_STORY: >>>
As a Zephyr RTOS user I want stack overflows to be caught immediately by hardware
rather than silently corrupting adjacent memory, so that the system enters a known
error state rather than continuing with undefined behaviour.
<<<
RELATIONS:
- TYPE: Parent
  VALUE: ZEP-SYRS-35

[REQUIREMENT]
UID: ZEP-SRS-42-6
STATUS: Active
TYPE: Functional
COMPONENT: Freedom From Interference
TITLE: Compiler stack canary protection
STATEMENT: >>>
When CONFIG_STACK_CANARIES (or a stronger variant) is enabled, the Zephyr RTOS
shall instrument functions with compiler-generated canary values that are verified
on function return; canary corruption shall trigger a fatal error for the running
entity.
<<<
USER_STORY: >>>
As a Zephyr RTOS user I want buffer overflow attacks or bugs that overwrite the
stack frame to be detected before the corrupted return address is used, so that
control flow is not redirected to attacker-controlled code.
<<<
RELATIONS:
- TYPE: Parent
  VALUE: ZEP-SYRS-35

[REQUIREMENT]
UID: ZEP-SRS-42-7
STATUS: Active
TYPE: Functional
COMPONENT: Freedom From Interference
TITLE: Software stack sentinel periodic check
STATEMENT: >>>
When CONFIG_STACK_SENTINEL is enabled, the Zephyr RTOS shall store a magic value
at the lowest address of each thread stack and verify its integrity at context
switch (outgoing thread), at non-context-switching hardware interrupts (for the
interrupted thread), upon thread entry-point return, and when a thread calls
k_yield() without context-switching; detection of sentinel corruption shall invoke
the fatal error handler for the thread.
<<<
USER_STORY: >>>
As a Zephyr RTOS user on a platform without hardware stack protection, I want a
software fallback that detects stack overflow at the earliest observable checkpoint
so that silent corruption is caught before it causes unpredictable behaviour.
<<<
RELATIONS:
- TYPE: Parent
  VALUE: ZEP-SYRS-35

[REQUIREMENT]
UID: ZEP-SRS-42-8
STATUS: Active
TYPE: Functional
COMPONENT: Freedom From Interference
TITLE: Stack low-watermark threshold monitoring with callback
STATEMENT: >>>
When CONFIG_THREAD_RUNTIME_STACK_SAFETY is enabled, the Zephyr RTOS shall monitor
each thread's remaining free stack space and invoke a user-defined handler when the
unused stack fraction falls below a configured percentage threshold, allowing the
application to take corrective action before overflow occurs.
<<<
USER_STORY: >>>
As a Zephyr RTOS user I want early warning before a thread's stack is exhausted so
that I can increase the stack size or shed work before an overflow occurs.
<<<
RELATIONS:
- TYPE: Parent
  VALUE: ZEP-SYRS-35

[REQUIREMENT]
UID: ZEP-SRS-42-9
STATUS: Draft
TYPE: Non-Functional
COMPONENT: Freedom From Interference
TITLE: Deterministic containment of supervisor-mode stack overflow
STATEMENT: >>>
A stack overflow occurring in a supervisor-mode thread shall be deterministically
detected and shall prevent further corruption of memory outside the overflowing
thread's stack region, guaranteeing that the rest of the system (other threads and
kernel data structures) remains in a consistent state.

NOTE: This requirement is not fully met by the current Zephyr implementation.
CONFIG_HW_STACK_PROTECTION's Kconfig help text explicitly states: "This does not
necessarily prevent corruption and assertions about the overall system state when a
fault is triggered cannot be made." The gap is that hardware detection on some
architectures fires only after the first write beyond the guard region, which may
have already corrupted adjacent data.
<<<
USER_STORY: >>>
As a Zephyr RTOS user building a safety-critical system, I need a guarantee that a
stack overflow in any thread cannot silently corrupt kernel state or other threads'
data, because partial corruption leads to undefined behaviour that is harder to
diagnose than an immediate system halt.
<<<
RELATIONS:
- TYPE: Parent
  VALUE: ZEP-SYRS-35

[TEXT]
STATEMENT: >>>
Temporal Isolation
<<<

[REQUIREMENT]
UID: ZEP-SRS-42-10
STATUS: Active
TYPE: Functional
COMPONENT: Freedom From Interference
TITLE: Per-thread CPU cycle usage accounting
STATEMENT: >>>
When CONFIG_THREAD_RUNTIME_STATS is enabled, the Zephyr RTOS shall maintain per-thread
accumulated CPU cycle counts, updated at every context switch, and shall expose these
counts through the thread runtime statistics API so that CPU usage per thread can be
observed at runtime.
<<<
USER_STORY: >>>
As a Zephyr RTOS user I want to measure how much CPU time each thread has consumed
so that I can detect threads that are using more processor time than expected and
diagnose temporal interference.
<<<
RELATIONS:
- TYPE: Parent
  VALUE: ZEP-SYRS-35

[REQUIREMENT]
UID: ZEP-SRS-42-11
STATUS: Active
TYPE: Functional
COMPONENT: Freedom From Interference
TITLE: Configurable per-thread timeslice with expiry notification
STATEMENT: >>>
When CONFIG_TIMESLICE_PER_THREAD is enabled, the Zephyr RTOS shall support
configuration of an individual timeslice duration for each preemptible thread and
shall invoke a user-defined callback when a thread's timeslice expires, allowing
the application to enforce thread-specific CPU time policies.
<<<
USER_STORY: >>>
As a Zephyr RTOS user I want to assign different CPU time budgets to threads of the
same priority so that a computationally intensive thread cannot starve other threads
at the same priority level indefinitely.
<<<
RELATIONS:
- TYPE: Parent
  VALUE: ZEP-SYRS-35

[REQUIREMENT]
UID: ZEP-SRS-42-12
STATUS: Draft
TYPE: Functional
COMPONENT: Freedom From Interference
TITLE: Enforced CPU time budget with deterministic response
STATEMENT: >>>
The Zephyr RTOS shall provide a mechanism to assign a maximum CPU time budget to a
thread over a defined period, and shall apply a deterministic, configurable action
(such as thread suspension or priority demotion) when the thread exhausts its budget,
without requiring intervention from the application.

NOTE: This requirement is not currently met by the Zephyr implementation.
CONFIG_TIMESLICE_PER_THREAD provides an expiry callback but the enforcement action
is left entirely to the application callback; the kernel does not autonomously
enforce a budget. There is no sliding-window quota mechanism.
<<<
USER_STORY: >>>
As a Zephyr RTOS user building a mixed-criticality system, I want the kernel to
automatically demote or suspend a thread that exceeds its CPU time allocation without
relying on that thread's cooperation, so that a runaway lower-criticality thread
cannot indefinitely deny CPU time to higher-criticality threads at the same priority.
<<<
RELATIONS:
- TYPE: Parent
  VALUE: ZEP-SYRS-35

[REQUIREMENT]
UID: ZEP-SRS-42-13
STATUS: Draft
TYPE: Non-Functional
COMPONENT: Freedom From Interference
TITLE: Bounded and documented worst-case interrupt latency
STATEMENT: >>>
For a given Zephyr configuration and target hardware, the kernel shall specify a
documented upper bound on the worst-case interrupt latency, defined as the maximum
number of CPU cycles elapsed from hardware interrupt assertion to first instruction
of the ISR, taking into account all possible kernel critical sections and interrupt
lock durations in that configuration.

NOTE: This requirement is not currently met by the Zephyr implementation. Zephyr
does not formally specify or verify worst-case interrupt latency bounds. Critical
section lengths vary with configuration options and are not guaranteed or published
per-configuration. This is a prerequisite for hard real-time and safety-certification
(IEC 61508, ISO 26262) use cases.
<<<
USER_STORY: >>>
As a Zephyr RTOS user building a hard real-time or safety-certified system, I need a
published worst-case interrupt latency figure so that I can perform timing analysis
and demonstrate that all deadlines are met under worst-case conditions.
<<<
RELATIONS:
- TYPE: Parent
  VALUE: ZEP-SYRS-35

[TEXT]
STATEMENT: >>>
Fault Containment
<<<

[REQUIREMENT]
UID: ZEP-SRS-42-14
STATUS: Active
TYPE: Functional
COMPONENT: Freedom From Interference
TITLE: User thread fault containment
STATEMENT: >>>
When CONFIG_USERSPACE is enabled, a fatal error in a user-mode thread (such as an
MPU fault, illegal instruction, or unhandled exception) shall be contained to the
faulting thread: the thread shall be aborted and the kernel and other threads shall
remain operational and unaffected.
<<<
USER_STORY: >>>
As a Zephyr RTOS user I want a misbehaving user thread to be terminated without
bringing down the entire system so that other components can continue operating or
take corrective action.
<<<
RELATIONS:
- TYPE: Parent
  VALUE: ZEP-SYRS-35

[REQUIREMENT]
UID: ZEP-SRS-42-15
STATUS: Active
TYPE: Functional
COMPONENT: Freedom From Interference
TITLE: System call argument validation for user threads
STATEMENT: >>>
When CONFIG_USERSPACE is enabled, the Zephyr RTOS shall validate all arguments
supplied by a user-mode thread to a system call — including pointer bounds, object
ownership, and parameter ranges — before any privileged operation is performed;
any validation failure shall cause the calling thread to be terminated without
affecting the kernel or other threads.
<<<
USER_STORY: >>>
As a Zephyr RTOS user I want the kernel to reject malformed system calls from user
threads so that a buggy or malicious user thread cannot cause kernel corruption or
privilege escalation by passing crafted arguments.
<<<
RELATIONS:
- TYPE: Parent
  VALUE: ZEP-SYRS-35

[REQUIREMENT]
UID: ZEP-SRS-42-16
STATUS: Draft
TYPE: Functional
COMPONENT: Freedom From Interference
TITLE: Supervisor thread fault containment
STATEMENT: >>>
A fatal error occurring in a supervisor-mode thread shall not unconditionally
terminate the entire system; the Zephyr RTOS shall provide a mechanism by which
the fault is contained to the affected supervisor thread (or a defined fault
partition), allowing the rest of the system to continue operating or transition to
a safe state.

NOTE: This requirement is not currently met by the Zephyr implementation. A fatal
error in any supervisor-mode thread results in a kernel panic that halts the entire
system. Supervisor threads are not isolated from each other or from the kernel; there
is no intra-kernel fault containment mechanism. This is a fundamental architectural
gap for mixed-criticality deployments where kernel threads of different criticality
levels coexist.
<<<
USER_STORY: >>>
As a Zephyr RTOS user deploying a mixed-criticality system, I want a fault in a
lower-criticality supervisor-mode component to be contained so that
higher-criticality supervisor threads (e.g., a safety monitor or watchdog) can
continue executing and bring the system to a defined safe state.
<<<
RELATIONS:
- TYPE: Parent
  VALUE: ZEP-SYRS-35

[REQUIREMENT]
UID: ZEP-SRS-42-18
STATUS: Active
TYPE: Functional
COMPONENT: Freedom From Interference
TITLE: Per-thread MPU stack guard region
STATEMENT: >>>
When CONFIG_MPU_STACK_GUARD is enabled, the Zephyr RTOS shall configure a dedicated
MPU region as an unprivileged no-access guard at the bottom of every thread's stack
at context switch time, so that a write beyond the stack bottom generates an
immediate MPU fault for the exceeding thread regardless of privilege level.
<<<
USER_STORY: >>>
As a Zephyr RTOS user on an ARM or ARC platform, I want each thread to have a
hardware guard region protecting the boundary at the base of its stack so that a
stack overflow is caught immediately by the MPU rather than silently overwriting
adjacent memory.
<<<
RELATIONS:
- TYPE: Parent
  VALUE: ZEP-SYRS-35

[TEXT]
STATEMENT: >>>
Health Monitoring and Watchdog
<<<

[REQUIREMENT]
UID: ZEP-SRS-42-19
STATUS: Active
TYPE: Functional
COMPONENT: Freedom From Interference
TITLE: Hardware watchdog driver API
STATEMENT: >>>
The Zephyr RTOS shall provide a standardised hardware watchdog driver API
(wdt_setup, wdt_install_timeout, wdt_feed, wdt_disable) that allows an application
to configure one or more timeout channels on a hardware watchdog peripheral, register
a callback for the pre-reset warning window, and periodically feed each channel to
prevent a system reset.
<<<
USER_STORY: >>>
As a Zephyr RTOS user I want a portable API to configure and feed a hardware
watchdog so that a global system lockup or infinite loop in any component is
detected within a bounded time and the system is reset to a known state.
<<<
RELATIONS:
- TYPE: Parent
  VALUE: ZEP-SYRS-35

[REQUIREMENT]
UID: ZEP-SRS-42-20
STATUS: Active
TYPE: Functional
COMPONENT: Freedom From Interference
TITLE: Per-thread task-level software watchdog
STATEMENT: >>>
When CONFIG_TASK_WDT is enabled, the Zephyr RTOS shall provide a software watchdog
subsystem that assigns an independent timeout channel to each monitored thread via
task_wdt_add(), requires periodic feeding via task_wdt_feed(), and invokes a
per-channel application callback when any channel's timeout expires without being
fed. When no callback is registered, the subsystem shall trigger a system reboot.
The subsystem shall optionally back its internal timer with a hardware watchdog
(CONFIG_TASK_WDT_HW_FALLBACK) so that a lockup in the task watchdog itself is also
detected.
<<<
USER_STORY: >>>
As a Zephyr RTOS user I want to monitor the liveness of individual threads
independently so that a deadlock, priority inversion, or hang in any single thread
is detected and handled within a configured time window, even on hardware that
provides only a single watchdog channel.
<<<
RELATIONS:
- TYPE: Parent
  VALUE: ZEP-SYRS-35

[REQUIREMENT]
UID: ZEP-SRS-42-21
STATUS: Active
TYPE: Functional
COMPONENT: Freedom From Interference
TITLE: Multi-stage watchdog timeout escalation
STATEMENT: >>>
When CONFIG_WDT_MULTISTAGE is enabled, the Zephyr RTOS watchdog driver API shall
support multi-stage timeout configurations where each stage can be linked to the
next, allowing progressive escalation (for example: first stage triggers a callback
for diagnostic logging; second stage triggers a CPU core or SoC reset), giving the
application an opportunity to perform corrective action before a hard reset occurs.
<<<
USER_STORY: >>>
As a Zephyr RTOS user I want a pre-reset warning stage in the watchdog timeout
sequence so that I can capture diagnostic information (e.g., register dump, fault
log) before the system resets, aiding post-mortem analysis.
<<<
RELATIONS:
- TYPE: Parent
  VALUE: ZEP-SYRS-35

[REQUIREMENT]
UID: ZEP-SRS-42-22
STATUS: Active
TYPE: Functional
COMPONENT: Freedom From Interference
TITLE: Watchdog suspend and resume across power state transitions
STATEMENT: >>>
The Zephyr RTOS task watchdog shall provide task_wdt_suspend() and task_wdt_resume()
APIs to pause all watchdog channels before entering a system low-power state and
resume them after waking, preventing spurious watchdog expirations caused by the
system being intentionally idle.
<<<
USER_STORY: >>>
As a Zephyr RTOS user implementing power management, I want watchdog channels to be
automatically paused when the system enters sleep so that a legitimate low-power
idle does not trigger a watchdog reset.
<<<
RELATIONS:
- TYPE: Parent
  VALUE: ZEP-SYRS-35

[REQUIREMENT]
UID: ZEP-SRS-42-23
STATUS: Draft
TYPE: Functional
COMPONENT: Freedom From Interference
TITLE: Kernel thread liveness monitoring
STATEMENT: >>>
The Zephyr RTOS shall provide a mechanism to periodically verify that all registered
supervisor-mode threads are making forward progress, and shall invoke a configurable
response action (such as thread restart, safe-state entry, or system reboot) when a
monitored thread fails to demonstrate progress within a defined period.

NOTE: This requirement is not fully met by the current Zephyr implementation.
CONFIG_THREAD_MONITOR maintains a list of live threads but provides no periodic
liveness check and no automatic response when a thread stalls. CONFIG_TASK_WDT
supports per-thread monitoring but requires that each thread explicitly calls
task_wdt_feed(), meaning a thread that is stuck in kernel code without calling
task_wdt_feed() will not be detected until its channel timeout expires. There is
no kernel-internal progress verification that does not rely on thread cooperation.
<<<
USER_STORY: >>>
As a Zephyr RTOS user building a safety-critical system, I want the kernel to
detect automatically when any supervisor thread stops making progress without
relying on that thread's own cooperation, so that a deadlocked or infinitely
looping kernel thread is detected and handled regardless of whether it reaches its
task_wdt_feed() call site.
<<<
RELATIONS:
- TYPE: Parent
  VALUE: ZEP-SYRS-35

[TEXT]
STATEMENT: >>>
Static Allocation Guarantee
<<<

[REQUIREMENT]
UID: ZEP-SRS-42-24
STATUS: Active
TYPE: Functional
COMPONENT: Freedom From Interference
TITLE: Compile-time static definition of all kernel object types
STATEMENT: >>>
The Zephyr RTOS shall provide compile-time static definition macros for every
kernel object type — including threads (K_THREAD_DEFINE), timers (K_TIMER_DEFINE),
semaphores (K_SEM_DEFINE), mutexes (K_MUTEX_DEFINE), memory slabs
(K_MEM_SLAB_DEFINE), private heaps (K_HEAP_DEFINE), work queues, event objects,
and message queues — so that all kernel objects required by an application can be
allocated at link time without any runtime allocation call.
<<<
USER_STORY: >>>
As a Zephyr RTOS user building a safety-critical or MISRA-compliant application,
I want to declare all kernel objects statically at compile time so that memory
layout is fully determined before execution begins, eliminating the possibility of
allocation failure at runtime.
<<<
RELATIONS:
- TYPE: Parent
  VALUE: ZEP-SYRS-35

[REQUIREMENT]
UID: ZEP-SRS-42-25
STATUS: Active
TYPE: Functional
COMPONENT: Freedom From Interference
TITLE: Disabling the system heap to prohibit dynamic allocation
STATEMENT: >>>
When CONFIG_KERNEL_MEM_POOL is disabled or CONFIG_HEAP_MEM_POOL_SIZE is set to zero
and no subsystem adds a HEAP_MEM_POOL_ADD_SIZE_* contribution, the Zephyr RTOS shall
not compile or link k_malloc(), k_calloc(), k_realloc(), or k_aligned_alloc() into
the application image, making any call to these functions a link-time error.

This provides a build-time enforcement point that prevents accidental introduction
of dynamic allocation into applications that require a static-only memory model.
<<<
USER_STORY: >>>
As a Zephyr RTOS user targeting IEC 61508 SIL or ISO 26262 ASIL certification, I
want to be able to configure the build so that no dynamic memory allocation function
is available, ensuring that the no-dynamic-allocation rule is enforced by the linker
rather than relying on code review alone.
<<<
RELATIONS:
- TYPE: Parent
  VALUE: ZEP-SYRS-35

[REQUIREMENT]
UID: ZEP-SRS-42-26
STATUS: Active
TYPE: Functional
COMPONENT: Freedom From Interference
TITLE: Deterministic O(1) memory slab allocation
STATEMENT: >>>
The Zephyr RTOS memory slab (k_mem_slab) shall provide fixed-block allocation and
release from a statically pre-allocated pool with O(1) worst-case time, bounded
memory consumption equal to the declared block count times block size, and a
defined failure behaviour (return -ENOMEM) when no free block is available, so
that timing and memory-bound properties of the allocating code path are fully
analysable at design time.
<<<
USER_STORY: >>>
As a Zephyr RTOS user I want a memory allocator whose worst-case allocation time
and maximum memory consumption are known at design time so that I can use it in
time-critical code paths and demonstrate determinism to a safety assessor.
<<<
RELATIONS:
- TYPE: Parent
  VALUE: ZEP-SYRS-35

[REQUIREMENT]
UID: ZEP-SRS-42-27
STATUS: Draft
TYPE: Non-Functional
COMPONENT: Freedom From Interference
TITLE: Build-time guard against subsystem-forced dynamic allocation
STATEMENT: >>>
The Zephyr RTOS build system shall provide a configuration mechanism to detect and
reject any configuration where an enabled subsystem implicitly raises the effective
heap pool size above zero (via HEAP_MEM_POOL_ADD_SIZE_* contributions) when the
application has explicitly set CONFIG_HEAP_MEM_POOL_SIZE to zero and opted out of
dynamic allocation.

NOTE: This requirement is not currently met by the Zephyr implementation. The
current HEAP_MEM_POOL_ADD_SIZE_* override mechanism silently increases the system
heap to meet subsystem minimums even when the application has set
CONFIG_HEAP_MEM_POOL_SIZE=0, unless CONFIG_HEAP_MEM_POOL_IGNORE_MIN is also
set. There is no Kconfig warning or error that alerts the developer when a
subsystem forces dynamic allocation to become available against the application's
intent.
<<<
USER_STORY: >>>
As a Zephyr RTOS user who has explicitly prohibited dynamic allocation in my
safety-critical application, I want the build to fail with a clear diagnostic if
any enabled subsystem would silently re-enable dynamic allocation, so that the
static-only memory model is enforced comprehensively rather than depending on
developer awareness of HEAP_MEM_POOL_ADD_SIZE contributions.
<<<
RELATIONS:
- TYPE: Parent
  VALUE: ZEP-SYRS-35

[TEXT]
STATEMENT: >>>
Resource Isolation
<<<

[REQUIREMENT]
UID: ZEP-SRS-42-17
STATUS: Draft
TYPE: Functional
COMPONENT: Freedom From Interference
TITLE: Kernel object pool exhaustion isolation
STATEMENT: >>>
The Zephyr RTOS shall provide a mechanism to limit the number of kernel objects
(such as timers, memory slab blocks, or semaphore allocations) that can be held or
consumed by a single thread or memory domain, so that exhaustion of a shared resource
pool by one component cannot deny service to other components.

NOTE: This requirement is not currently met by the Zephyr implementation. All threads
share global kernel object pools without per-thread or per-domain quotas. A single
thread can exhaust a pool (e.g., a k_mem_slab) and starve other threads that depend
on it. There is no resource budgeting or accounting mechanism at the kernel object
level.
<<<
USER_STORY: >>>
As a Zephyr RTOS user building a safety-critical system, I want to guarantee that a
lower-criticality thread cannot consume all available timer or memory objects and
thereby cause a higher-criticality thread to fail when it requests a resource.
<<<
RELATIONS:
- TYPE: Parent
  VALUE: ZEP-SYRS-35
