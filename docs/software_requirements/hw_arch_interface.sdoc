[DOCUMENT]
TITLE: Hardware Architecture Interface
PREFIX: ZEP-SRS-19-

[GRAMMAR]
IMPORT_FROM_FILE: software_requirements.sgra

[TEXT]
STATEMENT: >>>
SPDX-License-Identifier: Apache-2.0
<<<

[REQUIREMENT]
UID: ZEP-SRS-19-1
STATUS: Draft
TYPE: Functional
COMPONENT: Hardware Architecture Interface
TITLE: Atomic Operations
STATEMENT: >>>
The Zephyr RTOS shall provide an interface functionality to access memory while ensuring mutual exclusion. Note: Implementation by atomic variables and accessing them by APIs.
<<<
USER_STORY: >>>
As a Zephyr RTOS user I want to read from or write into a memory areas without being disturbed by other threads or ISRs.
<<<
RELATIONS:
- TYPE: Parent
  VALUE: ZEP-SYRS-1

[REQUIREMENT]
UID: ZEP-SRS-19-2
STATUS: Draft
TYPE: Functional
COMPONENT: Hardware Architecture Interface
TITLE: Thread Context Switching
STATEMENT: >>>
The Zephyr RTOS shall provide a mechanism for context switching between threads.
<<<
USER_STORY: >>>
As a Zephyr RTOS user I want to execute code concurrently in one or more threads and when interrupted at a code location in a thread, to continue at the very same location.
<<<
RELATIONS:
- TYPE: Parent
  VALUE: ZEP-SYRS-1

[REQUIREMENT]
UID: ZEP-SRS-19-3
STATUS: Draft
TYPE: Functional
COMPONENT: Hardware Architecture Interface
TITLE: Software Exceptions
STATEMENT: >>>
The Zephyr RTOS shall provide an interface to implement software exceptions.
<<<
USER_STORY: >>>
As a Zephyr RTOS user I want to catch any software exception and handle it according to my application needs.
<<<
RELATIONS:
- TYPE: Parent
  VALUE: ZEP-SYRS-1

[REQUIREMENT]
UID: ZEP-SRS-19-4
STATUS: Draft
TYPE: Functional
COMPONENT: Hardware Architecture Interface
TITLE: Processor Mode Support
STATEMENT: >>>
The Zephyr RTOS shall provide an interface for managing processor modes.
<<<
USER_STORY: >>>
If MCU power state was meant here:
As a Zephyr RTOS user I want to control the MCU's power saving mode such e.g. operation, sleep, deep sleep or similar as supported by the selected MCU.
<<<
RELATIONS:
- TYPE: Parent
  VALUE: ZEP-SYRS-1
