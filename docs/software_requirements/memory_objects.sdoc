[DOCUMENT]
TITLE: Memory Objects
PREFIX: ZEP-SRS-9-

[GRAMMAR]
IMPORT_FROM_FILE: software_requirements.sgra

[TEXT]
STATEMENT: >>>
SPDX-License-Identifier: Apache-2.0
<<<

[REQUIREMENT]
UID: ZEP-SRS-9-1
STATUS: Draft
TYPE: Functional
COMPONENT: Memory Objects
TITLE: Heap memory allocation
STATEMENT: >>>
The Zephyr RTOS shall provide an interface to allocate a variable-sized block of memory
from a heap object at runtime.
<<<
USER_STORY: >>>
As a Zephyr RTOS user, I want my application to be able to dynamically allocate memory
of an application-defined size from a named heap region.
<<<
RELATIONS:
- TYPE: Parent
  VALUE: ZEP-SYRS-9

[REQUIREMENT]
UID: ZEP-SRS-9-2
STATUS: Draft
TYPE: Functional
COMPONENT: Memory Objects
TITLE: Heap memory deallocation
STATEMENT: >>>
The Zephyr RTOS shall provide an interface to release a previously allocated variable-sized
memory block back to its heap object.
<<<
RELATIONS:
- TYPE: Parent
  VALUE: ZEP-SYRS-9

[REQUIREMENT]
UID: ZEP-SRS-9-3
STATUS: Draft
TYPE: Functional
COMPONENT: Memory Objects
TITLE: Memory slab allocation
STATEMENT: >>>
The Zephyr RTOS shall provide an interface to allocate a fixed-sized memory block from a
memory slab object, blocking the calling thread until a block is available or the specified
timeout expires.
<<<
USER_STORY: >>>
As a Zephyr RTOS user, I want a deterministic, fragmentation-free memory allocation mechanism
that allocates fixed-size blocks with bounded allocation time.
<<<
RELATIONS:
- TYPE: Parent
  VALUE: ZEP-SYRS-9

[REQUIREMENT]
UID: ZEP-SRS-9-4
STATUS: Draft
TYPE: Functional
COMPONENT: Memory Objects
TITLE: Memory slab deallocation
STATEMENT: >>>
The Zephyr RTOS shall provide an interface to release a fixed-sized memory block back to
the memory slab from which it was allocated.
<<<
RELATIONS:
- TYPE: Parent
  VALUE: ZEP-SYRS-9

[REQUIREMENT]
UID: ZEP-SRS-9-5
STATUS: Draft
TYPE: Functional
COMPONENT: Memory Objects
TITLE: Memory slab free block count query
STATEMENT: >>>
The Zephyr RTOS shall provide an interface to query the number of unused (free) blocks
remaining in a memory slab.
<<<
RELATIONS:
- TYPE: Parent
  VALUE: ZEP-SYRS-9

[REQUIREMENT]
UID: ZEP-SRS-9-6
STATUS: Draft
TYPE: Functional
COMPONENT: Memory Objects
TITLE: Memory slab used block count query
STATEMENT: >>>
The Zephyr RTOS shall provide an interface to query the number of allocated (in-use) blocks
in a memory slab.
<<<
RELATIONS:
- TYPE: Parent
  VALUE: ZEP-SYRS-9

[REQUIREMENT]
UID: ZEP-SRS-9-7
STATUS: Draft
TYPE: Functional
COMPONENT: Memory Objects
TITLE: Heap definition at compile time
STATEMENT: >>>
The Zephyr RTOS shall provide a mechanism to define and statically allocate a heap
object and its backing memory region at compile time.
<<<
RELATIONS:
- TYPE: Parent
  VALUE: ZEP-SYRS-9

[REQUIREMENT]
UID: ZEP-SRS-9-8
STATUS: Draft
TYPE: Functional
COMPONENT: Memory Objects
TITLE: Heap initialization at runtime
STATEMENT: >>>
The Zephyr RTOS shall provide an interface to initialize a heap object over a
caller-supplied memory region at runtime.
<<<
RELATIONS:
- TYPE: Parent
  VALUE: ZEP-SYRS-9

[REQUIREMENT]
UID: ZEP-SRS-9-9
STATUS: Draft
TYPE: Functional
COMPONENT: Memory Objects
TITLE: Memory slab definition at compile time
STATEMENT: >>>
The Zephyr RTOS shall provide a mechanism to define and statically allocate a memory
slab object and its block array at compile time.
<<<
RELATIONS:
- TYPE: Parent
  VALUE: ZEP-SYRS-9

[REQUIREMENT]
UID: ZEP-SRS-9-10
STATUS: Draft
TYPE: Functional
COMPONENT: Memory Objects
TITLE: Memory slab initialization at runtime
STATEMENT: >>>
The Zephyr RTOS shall provide an interface to initialize a memory slab over a
caller-supplied buffer, specifying the block size and number of blocks, at runtime.
<<<
RELATIONS:
- TYPE: Parent
  VALUE: ZEP-SYRS-9

[REQUIREMENT]
UID: ZEP-SRS-9-11
STATUS: Draft
TYPE: Functional
COMPONENT: Memory Objects
TITLE: Memory slab peak used block count query
STATEMENT: >>>
The Zephyr RTOS shall provide an interface to query the maximum number of blocks that
have been simultaneously allocated from a memory slab since it was last initialized,
to support worst-case memory usage analysis.
<<<
RELATIONS:
- TYPE: Parent
  VALUE: ZEP-SYRS-9
