[DOCUMENT]
TITLE: Power Management
PREFIX: ZEP-SRS-13-

[GRAMMAR]
IMPORT_FROM_FILE: software_requirements.sgra

[TEXT]
STATEMENT: >>>
SPDX-License-Identifier: Apache-2.0
<<<

[REQUIREMENT]
UID: ZEP-SRS-13-1
STATUS: Draft
TYPE: Functional
COMPONENT: Power Management
TITLE: Power State Control
STATEMENT: >>>
The Zephyr RTOS shall provide control over changes to system power states.
<<<
USER_STORY: >>>
See ZEP104
+
When the power state is changed I want to get an notification in order for specific parts of my application to react accordingly.
<<<

[REQUIREMENT]
UID: ZEP-SRS-13-2
STATUS: Draft
TYPE: Functional
COMPONENT: Power Management
TITLE: Power Management
STATEMENT: >>>
TBD
<<<

[REQUIREMENT]
UID: ZEP-SRS-13-3
STATUS: Draft
TYPE: Functional
COMPONENT: Power Management
TITLE: Notification of changes to system power states
STATEMENT: >>>
The Zephyr RTOS shall provide notification of changes to system power states.
<<<
