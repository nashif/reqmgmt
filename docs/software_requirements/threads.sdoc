[DOCUMENT]
TITLE: Threads
PREFIX: ZEP-SRS-1-

[GRAMMAR]
IMPORT_FROM_FILE: software_requirements.sgra

[TEXT]
STATEMENT: >>>
SPDX-License-Identifier: Apache-2.0
<<<

[REQUIREMENT]
UID: ZEP-SRS-1-1
STATUS: Draft
TYPE: Functional
COMPONENT: Threads
TITLE: Creating threads
STATEMENT: >>>
The Zephyr RTOS shall provide an interface to create (start) a thread.
<<<
RELATIONS:
- TYPE: Parent
  VALUE: ZEP-SYRS-15
- TYPE: Parent
  VALUE: ZEP-SYRS-16

[REQUIREMENT]
UID: ZEP-SRS-1-2
STATUS: Draft
TYPE: Functional
COMPONENT: Threads
TITLE: Setting thread priority
STATEMENT: >>>
The Zephyr RTOS shall provide an interface to set a thread's priority.
<<<
RELATIONS:
- TYPE: Parent
  VALUE: ZEP-SYRS-17

[REQUIREMENT]
UID: ZEP-SRS-1-3
STATUS: Draft
TYPE: Functional
COMPONENT: Threads
TITLE: Suspending a thread
STATEMENT: >>>
The Zephyr RTOS shall provide an interface to suspend a thread.
<<<
RELATIONS:
- TYPE: Parent
  VALUE: ZEP-SYRS-15
- TYPE: Parent
  VALUE: ZEP-SYRS-16

[REQUIREMENT]
UID: ZEP-SRS-1-4
STATUS: Draft
TYPE: Functional
COMPONENT: Threads
TITLE: Resuming a suspended thread
STATEMENT: >>>
The Zephyr RTOS shall provide an interface to resume a suspended thread.
<<<
RELATIONS:
- TYPE: Parent
  VALUE: ZEP-SYRS-15
- TYPE: Parent
  VALUE: ZEP-SYRS-16

[REQUIREMENT]
UID: ZEP-SRS-1-5
STATUS: Draft
TYPE: Functional
COMPONENT: Threads
TITLE: Joining a thread
STATEMENT: >>>
The Zephyr RTOS shall provide an interface to join a thread, blocking the calling thread
until the specified thread terminates or the specified timeout expires.
<<<
RELATIONS:
- TYPE: Parent
  VALUE: ZEP-SYRS-15
- TYPE: Parent
  VALUE: ZEP-SYRS-16

[REQUIREMENT]
UID: ZEP-SRS-1-6
STATUS: Draft
TYPE: Functional
COMPONENT: Threads
TITLE: Deleting a thread
STATEMENT: >>>
The Zephyr RTOS shall provide an interface to delete (end) a thread.
<<<
RELATIONS:
- TYPE: Parent
  VALUE: ZEP-SYRS-15
- TYPE: Parent
  VALUE: ZEP-SYRS-16

[REQUIREMENT]
UID: ZEP-SRS-1-7
STATUS: Draft
TYPE: Functional
COMPONENT: Threads
TITLE: Thread states
STATEMENT: >>>
The Zephyr RTOS shall define a set of lifecycle states for each thread, including
at minimum: not started, running, ready, sleeping, waiting, and suspended.
<<<
USER_STORY: >>>
As a Zephyr RTOS user, I want to know in what state a specific thread is.
<<<
RELATIONS:
- TYPE: Parent
  VALUE: ZEP-SYRS-15
- TYPE: Parent
  VALUE: ZEP-SYRS-16

[REQUIREMENT]
UID: ZEP-SRS-1-8
STATUS: Draft
TYPE: Functional
COMPONENT: Threads
TITLE: Thread stack objects
STATEMENT: >>>
Every thread shall have its own dedicated stack.
<<<
USER_STORY: >>>
As a Zephyr RTOS user I want to be able to configure the stack size of a thread. And every thread shall have it's own dedicated stack.
<<<
RELATIONS:
- TYPE: Parent
  VALUE: ZEP-SYRS-15
- TYPE: Parent
  VALUE: ZEP-SYRS-16

[REQUIREMENT]
UID: ZEP-SRS-1-9
STATUS: Draft
TYPE: Functional
COMPONENT: Threads
TITLE: Thread privileges
STATEMENT: >>>
The Zephyr RTOS shall provide an interface to create threads with defined privilege.
<<<
RELATIONS:
- TYPE: Parent
  VALUE: ZEP-SYRS-15
- TYPE: Parent
  VALUE: ZEP-SYRS-16

[REQUIREMENT]
UID: ZEP-SRS-1-10
STATUS: Draft
TYPE: Functional
COMPONENT: Threads
TITLE: Scheduling multiple threads
STATEMENT: >>>
The Zephyr RTOS shall provide an interface to schedule multiple threads.
<<<
RELATIONS:
- TYPE: Parent
  VALUE: ZEP-SYRS-16

[REQUIREMENT]
UID: ZEP-SRS-1-11
STATUS: Draft
TYPE: Functional
COMPONENT: Threads
TITLE: Thread Options
STATEMENT: >>>
The Zephyr RTOS shall support a set of thread options.
<<<
USER_STORY: >>>
As a Zephyr RTOS user, I want to be able to pass specific option to a thread.
<<<
RELATIONS:
- TYPE: Parent
  VALUE: ZEP-SYRS-15
- TYPE: Parent
  VALUE: ZEP-SYRS-16

[REQUIREMENT]
UID: ZEP-SRS-1-12
STATUS: Draft
TYPE: Functional
COMPONENT: Threads
TITLE: Thread custom data
STATEMENT: >>>
Every thread shall have a custom data area that can be set and read by the
application, accessible only by the thread itself.
<<<
RELATIONS:
- TYPE: Parent
  VALUE: ZEP-SYRS-15
- TYPE: Parent
  VALUE: ZEP-SYRS-16

[REQUIREMENT]
UID: ZEP-SRS-1-13
STATUS: Draft
TYPE: Functional
COMPONENT: Threads
TITLE: Yielding the CPU
STATEMENT: >>>
The Zephyr RTOS shall provide an interface for the current thread to voluntarily
yield the CPU to other ready threads of equal or higher priority.
<<<
RELATIONS:
- TYPE: Parent
  VALUE: ZEP-SYRS-15
- TYPE: Parent
  VALUE: ZEP-SYRS-16

[REQUIREMENT]
UID: ZEP-SRS-1-15
STATUS: Draft
TYPE: Functional
COMPONENT: Threads
TITLE: Static thread definition at compile time
STATEMENT: >>>
The Zephyr RTOS shall provide a mechanism to define and statically create a thread,
including its stack and initial parameters, at compile time without calling
k_thread_create() at runtime.
<<<
RELATIONS:
- TYPE: Parent
  VALUE: ZEP-SYRS-15
- TYPE: Parent
  VALUE: ZEP-SYRS-16

[REQUIREMENT]
UID: ZEP-SRS-1-16
STATUS: Draft
TYPE: Functional
COMPONENT: Threads
TITLE: Reading thread priority
STATEMENT: >>>
The Zephyr RTOS shall provide an interface to read the current numeric scheduling
priority of a specified thread.
<<<
RELATIONS:
- TYPE: Parent
  VALUE: ZEP-SYRS-17

[REQUIREMENT]
UID: ZEP-SRS-1-17
STATUS: Draft
TYPE: Functional
COMPONENT: Threads
TITLE: Getting the current thread identifier
STATEMENT: >>>
The Zephyr RTOS shall provide an interface to retrieve the thread identifier of the
currently executing thread.
<<<
RELATIONS:
- TYPE: Parent
  VALUE: ZEP-SYRS-15

[REQUIREMENT]
UID: ZEP-SRS-1-18
STATUS: Draft
TYPE: Functional
COMPONENT: Threads
TITLE: Thread stack usage monitoring
STATEMENT: >>>
The Zephyr RTOS shall provide an interface to query the unused stack space remaining
for a specified thread, to support detection of stack overflow conditions.
<<<
USER_STORY: >>>
As a safety-critical application developer, I need to monitor each thread's remaining
stack space at runtime to detect and respond to stack overflow conditions before memory
is corrupted.
<<<
RELATIONS:
- TYPE: Parent
  VALUE: ZEP-SYRS-15
- TYPE: Parent
  VALUE: ZEP-SYRS-16

[REQUIREMENT]
UID: ZEP-SRS-1-14
STATUS: Draft
TYPE: Functional
COMPONENT: Threads
TITLE: Thread name
STATEMENT: >>>
The Zephyr RTOS shall provide an interface to assign and retrieve a human-readable
name string for a thread, to aid in debugging and tracing.
<<<
RELATIONS:
- TYPE: Parent
  VALUE: ZEP-SYRS-15
- TYPE: Parent
  VALUE: ZEP-SYRS-16
