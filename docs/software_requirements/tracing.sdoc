[DOCUMENT]
TITLE: Tracing
PREFIX: ZEP-SRS-10-

[GRAMMAR]
IMPORT_FROM_FILE: software_requirements.sgra

[TEXT]
STATEMENT: >>>
SPDX-License-Identifier: Apache-2.0
<<<

[REQUIREMENT]
UID: ZEP-SRS-10-1
STATUS: Draft
TYPE: Functional
COMPONENT: Tracing
TITLE: Initializing a trace
STATEMENT: >>>
The Zephyr RTOS shall provide an interface to initialize a trace.
<<<
RELATIONS:
- TYPE: Parent
  VALUE: ZEP-SYRS-19

[REQUIREMENT]
UID: ZEP-SRS-10-2
STATUS: Draft
TYPE: Functional
COMPONENT: Tracing
TITLE: Triggering a trace
STATEMENT: >>>
The Zephyr RTOS shall provide an interface to trigger a trace.
<<<
RELATIONS:
- TYPE: Parent
  VALUE: ZEP-SYRS-19

[REQUIREMENT]
UID: ZEP-SRS-10-3
STATUS: Draft
TYPE: Functional
COMPONENT: Tracing
TITLE: Dumping trace results
STATEMENT: >>>
The Zephyr RTOS shall provide an interface to dump results from a trace.
<<<
RELATIONS:
- TYPE: Parent
  VALUE: ZEP-SYRS-19

[REQUIREMENT]
UID: ZEP-SRS-10-4
STATUS: Draft
TYPE: Functional
COMPONENT: Tracing
TITLE: Removing trace data
STATEMENT: >>>
The Zephyr RTOS shall provide an interface to remove trace data.
<<<
RELATIONS:
- TYPE: Parent
  VALUE: ZEP-SYRS-19

[REQUIREMENT]
UID: ZEP-SRS-10-5
STATUS: Draft
TYPE: Functional
COMPONENT: Tracing
TITLE: Tracing object identification
STATEMENT: >>>
The Zephyr RTOS shall provide an interface to identify the objects being traced.
<<<
USER_STORY: >>>
As a Zephyr RTOS user, I want to be able to give each object which I create a name
or label in order to be able to identify them in a trace log.
<<<
RELATIONS:
- TYPE: Parent
  VALUE: ZEP-SYRS-19

[REQUIREMENT]
UID: ZEP-SRS-10-6
STATUS: Draft
TYPE: Non-Functional
COMPONENT: Tracing
TITLE: Tracing non-interference
STATEMENT: >>>
When the tracing subsystem is disabled at compile time (CONFIG_TRACING not set),
all tracing hook macros (SYS_PORT_TRACING_FUNC, SYS_PORT_TRACING_OBJ_FUNC, and
all their variants) shall expand to empty statements that produce no executable
code, introducing zero runtime overhead to the instrumented kernel operations.

When the tracing subsystem is enabled, tracing hooks shall be purely observing:
they must not alter the execution path, return values, timing, or any observable
behavior of the kernel operation being traced.
<<<
USER_STORY: >>>
As a Zephyr RTOS user targeting a safety-critical or resource-constrained system,
I want the tracing functionality to have zero impact on the behavior and timing
of the system when tracing is disabled, and to be a non-intrusive observer that
does not change kernel behavior when tracing is enabled.
<<<
RELATIONS:
- TYPE: Parent
  VALUE: ZEP-SYRS-19
